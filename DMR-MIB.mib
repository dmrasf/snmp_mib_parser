--
-- DMR-MIB.mib
-- MIB generated by MG-SOFT Visual MIB Builder Version 6.0  Build 88
-- Friday, December 22, 2023 at 09:11:17
--

	DMR-MIB DEFINITIONS ::= BEGIN

		IMPORTS
			enterprises, Unsigned32, OBJECT-TYPE, MODULE-IDENTITY, NOTIFICATION-TYPE
				FROM SNMPv2-SMI
			DisplayString
				FROM SNMPv2-TC;


		-- 1.3.6.1.4.1.12345
		smartgen MODULE-IDENTITY
			LAST-UPDATED "202312181607Z"		-- December 18, 2023 at 16:07 GMT
			ORGANIZATION
				"SMARTGEN(ZHENGZHOU) TECHNOLOGY CO.,LTD."
			CONTACT-INFO
				"SMARTGEN(ZHENGZHOU) TECHNOLOGY CO.,LTD.
				Zhengzhou,China
				web: www.smartgen.com.cn"
			DESCRIPTION ""
			REVISION "202312181607Z"		-- December 18, 2023 at 16:07 GMT
			DESCRIPTION
				"Version:V1.0
				First revision.
				Author DMR"
			::= { enterprises 12345 }




--
-- Node definitions
--

--  Node definitions
--
-- 1.3.6.1.4.1.12345.1
		-- 1.3.6.1.4.1.12345.1
		cm02 OBJECT IDENTIFIER ::= { smartgen 1 }


-- ----------------------------------------------------------------------
-- ----------------------------------------------------------------------
-- ----------------------------------------------------------------------
--  1.3.6.1.4.1.12345.1.1
		-- 1.3.6.1.4.1.12345.1.1
		acDistribution OBJECT IDENTIFIER ::= { cm02 1 }


--  1.3.6.1.4.1.12345.1.1
		-- 1.3.6.1.4.1.12345.1.1.1
		acinfo OBJECT-TYPE
			SYNTAX Unsigned32
			MAX-ACCESS read-only
			STATUS current
			DESCRIPTION
				"AC"
			::= { acDistribution 1 }


-- ----------------------------------------------------------
		-- 1.3.6.1.4.1.12345.1.1.2
		dgInfo OBJECT IDENTIFIER ::= { acDistribution 2 }


-- ----------------------------------------------------------
-- DG counter { dgInfo 1 }
-- ----------------------------------------------------------
		-- 1.3.6.1.4.1.12345.1.1.2.1
		totalDGNumber OBJECT-TYPE
			SYNTAX INTEGER (0..3)
			ACCESS read-write
			STATUS current
			DESCRIPTION
				"
				The total number of the DG."
			::= { dgInfo 1 }


-- ----------------------------------------------------------
-- DG information table { dgInfo 2 }
-- ----------------------------------------------------------
		-- 1.3.6.1.4.1.12345.1.1.2.2
		dgInfoTable OBJECT-TYPE
			SYNTAX SEQUENCE OF DGInfoEntry
			MAX-ACCESS not-accessible
			STATUS current
			DESCRIPTION
				"
				Table holding information about the currently BMM."
			::= { dgInfo 2 }


		-- 1.3.6.1.4.1.12345.1.1.2.2.1
		dgInfoEntry OBJECT-TYPE
			SYNTAX DGInfoEntry
			MAX-ACCESS not-accessible
			STATUS current
			DESCRIPTION
				"
				An entry (conceptual row) in the dgInfoTable."
			INDEX { dgIndex }
			::= { dgInfoTable 1 }


		DGInfoEntry ::=
			SEQUENCE {
				dgIndex
					INTEGER,
				dgState
					INTEGER,
				oilPressure
					Unsigned32,
				fuelLevel
					Unsigned32,
				engineSpeed
					INTEGER,
				generatorFrequency
					INTEGER,
				generatorL1Nvoltage
					INTEGER,
				generatorL2Nvoltage
					INTEGER,
				generatorL3Nvoltage
					INTEGER,
				generatorL1L2voltage
					INTEGER,
				generatorL2L3voltage
					INTEGER,
				generatorL3L1voltage
					INTEGER,
				l1current
					INTEGER,
				l2current
					INTEGER,
				l3current
					INTEGER,
				earthCurrent
					INTEGER,
				l1watts
					INTEGER,
				l2watts
					INTEGER,
				l3watts
					INTEGER,
				mainsFrequency
					INTEGER,
				mainsL1Nvoltage
					INTEGER,
				mainsL2Nvoltage
					INTEGER,
				mainsL3Nvoltage
					INTEGER,
				mainsL1L2voltage
					INTEGER,
				mainsL2L3voltage
					INTEGER,
				mainsL3L1voltage
					INTEGER
			 }

		-- 1.3.6.1.4.1.12345.1.1.2.2.1.1
		dgIndex OBJECT-TYPE
			SYNTAX INTEGER
				{
				dg1(1),
				dg2(2),
				dg3(3)
				}
			MAX-ACCESS read-only
			STATUS current
			DESCRIPTION
				"
				The unique sequence number of this DG.
				DG1 (1),
				DG2  (2),
				DG3 (3),
				"
			::= { dgInfoEntry 1 }


		-- 1.3.6.1.4.1.12345.1.1.2.2.1.2
		dgState OBJECT-TYPE
			SYNTAX INTEGER
				{
				stop(0),
				running(1)
				}
			MAX-ACCESS read-only
			STATUS current
			DESCRIPTION
				"
				Status of DG.
				0:stop;1:running"
			::= { dgInfoEntry 2 }


		-- 1.3.6.1.4.1.12345.1.1.2.2.1.3
		oilPressure OBJECT-TYPE
			SYNTAX Unsigned32 (0..100)
			MAX-ACCESS read-only
			STATUS current
			DESCRIPTION
				"
				The oil pressure.
				 The actual value = The receive data/100.
				 The unit of actual value is Bar."
			::= { dgInfoEntry 3 }


		-- 1.3.6.1.4.1.12345.1.1.2.2.1.4
		fuelLevel OBJECT-TYPE
			SYNTAX Unsigned32 (0..100)
			MAX-ACCESS read-only
			STATUS current
			DESCRIPTION
				"
				Fuel level of DG.
				 The actual value = The receive data/100.
				 The unit of actual value is percent.
				 -100 means invaid.
				"
			::= { dgInfoEntry 4 }


		-- 1.3.6.1.4.1.12345.1.1.2.2.1.5
		engineSpeed OBJECT-TYPE
			SYNTAX INTEGER
			MAX-ACCESS read-only
			STATUS current
			DESCRIPTION
				"
				Engine speed of DG.
				 The actual value = The receive data/100.
				 The unit of actual value is RPM.
				"
			::= { dgInfoEntry 5 }


		-- 1.3.6.1.4.1.12345.1.1.2.2.1.6
		generatorFrequency OBJECT-TYPE
			SYNTAX INTEGER
			MAX-ACCESS read-only
			STATUS current
			DESCRIPTION
				"
				Generator frequency.
				 The actual value = The receive data/100.
				 The unit of actual value is Hz.
				"
			::= { dgInfoEntry 6 }


		-- 1.3.6.1.4.1.12345.1.1.2.2.1.7
		generatorL1Nvoltage OBJECT-TYPE
			SYNTAX INTEGER
			MAX-ACCESS read-only
			STATUS current
			DESCRIPTION
				"
				Generator L1-N voltage.
				 The actual value = The receive data/100.
				The unit of actual value is V."
			::= { dgInfoEntry 7 }


		-- 1.3.6.1.4.1.12345.1.1.2.2.1.8
		generatorL2Nvoltage OBJECT-TYPE
			SYNTAX INTEGER
			MAX-ACCESS read-only
			STATUS current
			DESCRIPTION
				"
				Generator L2-N voltage.
				 The actual value = The receive data/100.
				The unit of actual value is V."
			::= { dgInfoEntry 8 }


		-- 1.3.6.1.4.1.12345.1.1.2.2.1.9
		generatorL3Nvoltage OBJECT-TYPE
			SYNTAX INTEGER
			MAX-ACCESS read-only
			STATUS current
			DESCRIPTION
				"
				Generator L3-N voltage.
				 The actual value = The receive data/100.
				The unit of actual value is V."
			::= { dgInfoEntry 9 }


		-- 1.3.6.1.4.1.12345.1.1.2.2.1.10
		generatorL1L2voltage OBJECT-TYPE
			SYNTAX INTEGER
			MAX-ACCESS read-only
			STATUS current
			DESCRIPTION
				"
				Generator L1-L2 voltage.
				 The actual value = The receive data/100.
				The unit of actual value is V."
			::= { dgInfoEntry 10 }


		-- 1.3.6.1.4.1.12345.1.1.2.2.1.11
		generatorL2L3voltage OBJECT-TYPE
			SYNTAX INTEGER
			MAX-ACCESS read-only
			STATUS current
			DESCRIPTION
				"
				Generator L2-L3 voltage.
				 The actual value = The receive data/100.
				The unit of actual value is V."
			::= { dgInfoEntry 11 }


		-- 1.3.6.1.4.1.12345.1.1.2.2.1.12
		generatorL3L1voltage OBJECT-TYPE
			SYNTAX INTEGER
			MAX-ACCESS read-only
			STATUS current
			DESCRIPTION
				"
				Generator L3-L1 voltage.
				 The actual value = The receive data/100.
				The unit of actual value is V."
			::= { dgInfoEntry 12 }


		-- 1.3.6.1.4.1.12345.1.1.2.2.1.13
		l1current OBJECT-TYPE
			SYNTAX INTEGER
			MAX-ACCESS read-only
			STATUS current
			DESCRIPTION
				"
				Generator L1 current.
				 The actual value = The receive data/100.
				The unit of actual value is A."
			::= { dgInfoEntry 13 }


		-- 1.3.6.1.4.1.12345.1.1.2.2.1.14
		l2current OBJECT-TYPE
			SYNTAX INTEGER
			MAX-ACCESS read-only
			STATUS current
			DESCRIPTION
				"
				Generator L2 current.
				 The actual value = The receive data/100.
				The unit of actual value is A."
			::= { dgInfoEntry 14 }


		-- 1.3.6.1.4.1.12345.1.1.2.2.1.15
		l3current OBJECT-TYPE
			SYNTAX INTEGER
			MAX-ACCESS read-only
			STATUS current
			DESCRIPTION
				"
				Generator L3 current.
				 The actual value = The receive data/100.
				The unit of actual value is A."
			::= { dgInfoEntry 15 }


		-- 1.3.6.1.4.1.12345.1.1.2.2.1.16
		earthCurrent OBJECT-TYPE
			SYNTAX INTEGER
			MAX-ACCESS read-only
			STATUS current
			DESCRIPTION
				"
				Earth current.
				 The actual value = The receive data/100.
				The unit of actual value is A."
			::= { dgInfoEntry 16 }


		-- 1.3.6.1.4.1.12345.1.1.2.2.1.17
		l1watts OBJECT-TYPE
			SYNTAX INTEGER
			MAX-ACCESS read-only
			STATUS current
			DESCRIPTION
				"
				Generator L1 watts.
				 The actual value = The receive data/100.
				The unit of actual value is KW."
			::= { dgInfoEntry 17 }


		-- 1.3.6.1.4.1.12345.1.1.2.2.1.18
		l2watts OBJECT-TYPE
			SYNTAX INTEGER
			MAX-ACCESS read-only
			STATUS current
			DESCRIPTION
				"
				Generator L2 watts.
				 The actual value = The receive data/100.
				The unit of actual value is KW."
			::= { dgInfoEntry 18 }


		-- 1.3.6.1.4.1.12345.1.1.2.2.1.19
		l3watts OBJECT-TYPE
			SYNTAX INTEGER
			MAX-ACCESS read-only
			STATUS current
			DESCRIPTION
				"
				Generator L3 watts.
				 The actual value = The receive data/100.
				The unit of actual value is KW."
			::= { dgInfoEntry 19 }


		-- 1.3.6.1.4.1.12345.1.1.2.2.1.20
		mainsFrequency OBJECT-TYPE
			SYNTAX INTEGER
			MAX-ACCESS read-only
			STATUS current
			DESCRIPTION
				"
				Mains frequency.
				 The actual value = The receive data/100.
				The unit of actual value is Hz."
			::= { dgInfoEntry 20 }


		-- 1.3.6.1.4.1.12345.1.1.2.2.1.21
		mainsL1Nvoltage OBJECT-TYPE
			SYNTAX INTEGER
			MAX-ACCESS read-only
			STATUS current
			DESCRIPTION
				"
				Mains L1-N voltage.
				 The actual value = The receive data/100.
				The unit of actual value is V."
			::= { dgInfoEntry 21 }


		-- 1.3.6.1.4.1.12345.1.1.2.2.1.22
		mainsL2Nvoltage OBJECT-TYPE
			SYNTAX INTEGER
			MAX-ACCESS read-only
			STATUS current
			DESCRIPTION
				"
				Mains L2-N voltage.
				 The actual value = The receive data/100.
				The unit of actual value is V."
			::= { dgInfoEntry 22 }


		-- 1.3.6.1.4.1.12345.1.1.2.2.1.23
		mainsL3Nvoltage OBJECT-TYPE
			SYNTAX INTEGER
			MAX-ACCESS read-only
			STATUS current
			DESCRIPTION
				"
				Mains L3-N voltage.
				 The actual value = The receive data/100.
				The unit of actual value is V."
			::= { dgInfoEntry 23 }


		-- 1.3.6.1.4.1.12345.1.1.2.2.1.24
		mainsL1L2voltage OBJECT-TYPE
			SYNTAX INTEGER
			MAX-ACCESS read-only
			STATUS current
			DESCRIPTION
				"
				Mains L1-L2 voltage.
				 The actual value = The receive data/100.
				The unit of actual value is V."
			::= { dgInfoEntry 24 }


		-- 1.3.6.1.4.1.12345.1.1.2.2.1.25
		mainsL2L3voltage OBJECT-TYPE
			SYNTAX INTEGER
			MAX-ACCESS read-only
			STATUS current
			DESCRIPTION
				"
				Mains L2-L3 voltage.
				 The actual value = The receive data/100.
				The unit of actual value is V."
			::= { dgInfoEntry 25 }


		-- 1.3.6.1.4.1.12345.1.1.2.2.1.26
		mainsL3L1voltage OBJECT-TYPE
			SYNTAX INTEGER
			MAX-ACCESS read-only
			STATUS current
			DESCRIPTION
				"
				Mains L3-L1 voltage.
				 The actual value = The receive data/100.
				The unit of actual value is V."
			::= { dgInfoEntry 26 }


-- ----------------------------------------------------------------------
-- ----------------------------------------------------------------------
-- ----------------------------------------------------------------------
--  1.3.6.1.4.1.12345.1.2
		-- 1.3.6.1.4.1.12345.1.2
		rectifier OBJECT IDENTIFIER ::= { cm02 2 }

		rectifier1 OBJECT-TYPE
			SYNTAX INTEGER
			MAX-ACCESS read-only
			STATUS current
			DESCRIPTION
				"rectifier1"
			::= { rectifier 1 }

		rectifier2 OBJECT-TYPE
			SYNTAX INTEGER
			MAX-ACCESS read-only
			STATUS current
			DESCRIPTION
				"rectifier1"
			::= { rectifier 4 }


-- ----------------------------------------------------------------------
-- ----------------------------------------------------------------------
-- ----------------------------------------------------------------------
--  1.3.6.1.4.1.12345.1.3
		-- 1.3.6.1.4.1.12345.1.3
		dcDistribution OBJECT IDENTIFIER ::= { cm02 3 }


-- ----------------------------------------------------------------------
-- ----------------------------------------------------------------------
-- ----------------------------------------------------------------------
--  1.3.6.1.4.1.12345.1.4
		-- 1.3.6.1.4.1.12345.1.4
		systemAlarm OBJECT IDENTIFIER ::= { cm02 4 }


		-- 1.3.6.1.4.1.12345.1.4.2
		alarmTable OBJECT-TYPE
			SYNTAX SEQUENCE OF AlarmEntry
			MAX-ACCESS not-accessible
			STATUS current
			DESCRIPTION			" "
			::= { systemAlarm 2 }


		-- 1.3.6.1.4.1.12345.1.4.2.1
		alarmEntry OBJECT-TYPE
			SYNTAX AlarmEntry
			MAX-ACCESS not-accessible
			STATUS current
			DESCRIPTION			" "
			INDEX { alarmIndex }
			::= { alarmTable 1 }


		AlarmEntry ::=
			SEQUENCE {
				alarmIndex INTEGER,
				alarmTime DisplayString,
				alarmLevel INTEGER,
				alarmType INTEGER,
				alarmRelateDOPosition INTEGER,
				alarmRelateDO INTEGER,
				alarmBuzzer INTEGER,
				alarmMoudleID INTEGER,
				alarmStatusChange INTEGER,
				alarmName DisplayString
			 }

		-- 1.3.6.1.4.1.12345.1.4.2.1.1
		alarmIndex OBJECT-TYPE
			SYNTAX INTEGER { ac1SlightOverCurrent(1) }
			MAX-ACCESS read-only
			STATUS current
			DESCRIPTION			" "
			::= { alarmEntry 1 }


		-- 1.3.6.1.4.1.12345.1.4.2.1.2
		alarmTime OBJECT-TYPE
			SYNTAX DisplayString
			MAX-ACCESS read-only
			STATUS current
			DESCRIPTION			" "
			::= { alarmEntry 2 }


		-- 1.3.6.1.4.1.12345.1.4.2.1.3
		alarmLevel OBJECT-TYPE
			SYNTAX INTEGER
				{
				minor(0),
				major(1),
				critical(2)
				}
			MAX-ACCESS read-only
			STATUS current
			DESCRIPTION
				"
				The severity of the alarm. One of
				(0) minor - MI, lowest level of alarm severity
				(1) major - MA
				(2) critical - CA, highest level of alarm severity"
			::= { alarmEntry 3 }


		-- 1.3.6.1.4.1.12345.1.4.2.1.4
		alarmType OBJECT-TYPE
			SYNTAX INTEGER
				{
				notUsed(0),
				acAlarm(1),
				dcAlarm(2)
				}
			MAX-ACCESS read-only
			STATUS current
			DESCRIPTION
				"
				Alarm type, i.e. an integer specifying the type of alarm.
				notUsed (0),
				acAlarm (1),
				dcAlarm (2),"
			::= { alarmEntry 4 }


		-- 1.3.6.1.4.1.12345.1.4.2.1.5
		alarmRelateDOPosition OBJECT-TYPE
			SYNTAX INTEGER
				{
				notUsed(0),
				controller(1),
				extendDOBorad1(2),
				extendDOBorad2(3),
				extendDOBorad3(4),
				extendDOBorad4(5),
				extendDOBorad5(6)
				}
			MAX-ACCESS read-only
			STATUS current
			DESCRIPTION
				"
				The position of the relay-out for the alarm.
				notUsed (0),
				controller (1),
				extendDOBorad1 (2),
				extendDOBorad2 (3),
				extendDOBorad3 (4),
				extendDOBorad4 (5),
				extendDOBorad5 (6)"
			::= { alarmEntry 5 }


		-- 1.3.6.1.4.1.12345.1.4.2.1.6
		alarmRelateDO OBJECT-TYPE
			SYNTAX INTEGER
				{
				relayOut1(0),
				relayOut2(1),
				relayOut3(2),
				relayOut4(3),
				relayOut5(4),
				relayOut6(5),
				relayOut7(6),
				relayOut8(7),
				relayOut9(8),
				relayOut10(9),
				relayOut11(10),
				relayOut12(11),
				relayOut13(12),
				relayOut14(13),
				relayOut15(14),
				relayOut16(15)
				}
			MAX-ACCESS read-only
			STATUS current
			DESCRIPTION
				"
				The relay-out number for the alarm.
				relayOut1 (0),
				relayOut2 (1),
				relayOut3 (2),
				relayOut4 (3),
				relayOut5 (4),
				relayOut6 (5),
				relayOut7 (6),
				relayOut8 (7),
				relayOut9 (8),
				relayOut10 (9),
				relayOut11 (10),
				relayOut12 (11),
				relayOut13 (12),
				relayOut14 (13),
				relayOut15 (14),
				relayOut16 (15)"
			::= { alarmEntry 6 }


		-- 1.3.6.1.4.1.12345.1.4.2.1.7
		alarmBuzzer OBJECT-TYPE
			SYNTAX INTEGER
				{
				silent(0),
				sound(1)
				}
			MAX-ACCESS read-only
			STATUS current
			DESCRIPTION
				"
				The alarm configuration for the buzzer.One of
				(0) silent - no sound for alarm
				(1) sound - sound for alarm"
			::= { alarmEntry 7 }


		-- 1.3.6.1.4.1.12345.1.4.2.1.8
		alarmMoudleID OBJECT-TYPE
			SYNTAX INTEGER { notMoudleAlarm(0) }
			MAX-ACCESS read-only
			STATUS current
			DESCRIPTION
				"
				The moudle ID number of the moudle.This is only for
				rectifierAlarm, solarControllerAlarm, windControllerAlarm,
				inverterAlarm, dcdcConverterAlarm.
				(0) not the moudle alarm
				(1..128) the moudle ID number of the moudle"
			::= { alarmEntry 8 }


		-- 1.3.6.1.4.1.12345.1.4.2.1.9
		alarmStatusChange OBJECT-TYPE
			SYNTAX INTEGER
				{
				deactivated(0),
				activated(1)
				}
			MAX-ACCESS read-only
			STATUS current
			DESCRIPTION
				"
				The status of alarm. One of
				(0) deactivated
				(1) activated"
			::= { alarmEntry 9 }


		-- 1.3.6.1.4.1.12345.1.4.2.1.10
		alarmName OBJECT-TYPE
			SYNTAX DisplayString
			MAX-ACCESS read-only
			STATUS current
			DESCRIPTION
				"Alarm name."
			::= { alarmEntry 10 }


		-- 1.3.6.1.4.1.12345.1.4.3
		systemTraps OBJECT IDENTIFIER ::= { systemAlarm 3 }


		-- 1.3.6.1.4.1.12345.1.4.3.1
		alarmTrap NOTIFICATION-TYPE
			OBJECTS { alarmIndex, alarmTime, alarmLevel, alarmType, alarmRelateDOPosition,
				alarmRelateDO, alarmBuzzer, alarmMoudleID, alarmStatusChange }
			STATUS current
			DESCRIPTION
				"
				An alarm trap is sent when an alarm occurs (activated) or
				returns to normal state (deactivated). Alarm traps are logged
				in alarmTrapTable. Variables in this trap:
				* alarmIndex - The unique sequence number of this alarm trap.
				* alarmTime - Date and time when event occured (local time),
					including timezone if supported by controller.
				* alarmLevel - Integer describing the severity of the alarm.
				* alarmType - Integer indicating type of alarm.
				* alarmRelateDOPosition - The position of the relay-out for the alarm.
				* alarmRelateDO - The relay-out number for the alarm.
				* alarmBuzzer - The alarm configuration for the buzzer.
				* alarmMoudleID - The moudle ID number of the moudle.
				* alarmStatusChange - The status of alarm."
			::= { systemTraps 1 }


-- ----------------------------------------------------------------------
-- ----------------------------------------------------------------------
-- ----------------------------------------------------------------------
--  1.3.6.1.4.1.12345.1.5
		-- 1.3.6.1.4.1.12345.1.5
		solarController OBJECT IDENTIFIER ::= { cm02 5 }


-- ----------------------------------------------------------------------
-- ----------------------------------------------------------------------
-- ----------------------------------------------------------------------
--  1.3.6.1.4.1.12345.1.6
		-- 1.3.6.1.4.1.12345.1.6
		dcdcConverter OBJECT IDENTIFIER ::= { cm02 6 }



	END

--
-- DMR-MIB.mib
--
